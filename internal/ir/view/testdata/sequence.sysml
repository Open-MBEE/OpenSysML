// The publish/subscribe interaction of the OMG sequence-modeling validation
// model: an occurrence definition whose parts hold the events the messages run
// between, ordered by member-attached successions.
package Sequences {
	private import ScalarValues::*;

	package PayloadDefinitions {
		item def Subscribe {
			attribute topic : String;
			ref part subscriber;
		}

		item def Publish {
			attribute topic : String;
			ref publication;
		}

		item def Deliver {
			ref publication;
		}
	}

	private import PayloadDefinitions::*;

	occurrence def PubSubSequence {
		part producer[1] {
			event occurrence publish_source_event;
		}

		message publish_message of Publish[1] from producer.publish_source_event to server.publish_target_event;

		part server[1] {
			event occurrence subscribe_target_event;
			then event occurrence publish_target_event;
			then event occurrence deliver_source_event;
		}

		message subscribe_message of Subscribe[1] from consumer.subscribe_source_event to server.subscribe_target_event;
		message deliver_message of Deliver[1] from server.deliver_source_event to consumer.deliver_target_event;

		part consumer[1] {
			event occurrence subscribe_source_event;
			then event occurrence deliver_target_event;
		}
	}
}

package SequenceViews {
	private import StandardViewDefinitions::*;

	// The rendering kind comes from the standard view definition.
	view pubSubView : SequenceView {
		expose Sequences::PubSubSequence;
	}
}
