// A document of the extent_across_documents case, indexed beside it: the Car it declares is
// reached by `all Car` taken in the other file, and first, its name sorting before that file's.
package depot {
    part van : fleet::Car;
}
