// A token reaching a merge along a succession that carries no value forwards the one
// a plain flow brought, never the one a succession flow brought for its own token.
package test {
	private import ScalarValues::*;
	action control {
		attribute ones : Integer = 0;
		attribute twos : Integer = 0;
		first start then split;
		fork split;
		first split then warm;
		first warm then a;
		action warm;
		first split then b;
		action a { out y : Integer; assign y := 1; }
		action b { out y : Integer; assign y := 2; }
		first b then relay;
		first relay then m;
		action relay;
		merge m {
			in ref inputObject1 : Integer;
			in ref inputObject2 : Integer;
			out ref outputObject1 : Integer = (inputObject1, inputObject2);
		}
		succession flow of Integer from a.y to m.inputObject1;
		flow b.y to m.inputObject2;
		action keep {
			in v : Integer;
			if v == 1 { assign ones := ones + 1; }
			if v == 2 { assign twos := twos + 1; }
		}
		succession flow of Integer from m.outputObject1 to keep.v;
	}
}
