package test {
	private import ScalarValues::*;
	private import SI::*;
	private import VectorFunctions::*;
	private import StateSpaceRepresentation::*;
	private import StateSpaceIntegration::*;

	attribute def FallState :> StateSpace;
	attribute def NoInput :> Input;
	attribute def HeightOutput :> Output;

	action def FreeFall :> ContinuousStateSpaceDynamics, FixedStepDynamics {
		in :>> input : NoInput = VectorOf((0.0));
		:>> stateSpace : FallState;

		calc :>> getDerivative {
			in input : NoInput;
			in stateSpace : FallState;
			return : StateDerivative = VectorOf((stateSpace.elements#(2), -9.81)) / 1 [s];
		}
		calc :>> getOutput {
			in input : NoInput;
			in stateSpace : FallState;
			return : HeightOutput = VectorOf((stateSpace.elements#(1)));
		}
		calc :>> getNextState { calc :>> integrate : RK4; }
	}

	action drop : FreeFall {
		:>> stateSpace = VectorOf((50.0, 0.0));
		:>> timeStep = 0.5 [s];
		:>> stopTime = 2 [s];
	}

	action fall : FreeFall {
		:>> stateSpace = VectorOf((100.0, 0.0));
		:>> timeStep = 1 [s];
		:>> stopTime = 3 [s];
	}
}
