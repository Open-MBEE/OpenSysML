package Model {
    item def Go;
    item def Enter;
    item def Dive;
    item def Resume;
    item def Skip;
    item def Next;
    item def Finish;
    item def Back;
    item def Stop;
    item def Pair;
    item def Split;
    item def Bump;
    occurrence def Station {
        attribute trace : ScalarValues::Integer default = 0;
        state def Cycle {
            in ref context : Station[1];
            entry; then Idle;
            state Idle;
            state Work parallel {
                entry action {
                    rep language "JavaScript" /* trace = trace * 100 + 11;*/
                    assign context.trace := context.trace * 100 + 11;
                }
                exit action {
                    rep language "JavaScript" /* trace = trace * 100 + 12;*/
                    assign context.trace := context.trace * 100 + 12;
                }
                state steps {
                    #StateMachines::junction state Start;
                    /* not migrated: Pseudostate 'Through' — (_tThrough) leads from the entry point straight to the exit point 'Leave' of the same state, crossing it without settling in it; the runtime would then run neither its entry nor its exit behavior */
                    #StateMachines::junction state Leave;
                    entry; then Prep;
                    state Prep {
                        entry action {
                            rep language "JavaScript" /* trace = trace * 100 + 13;*/
                            assign context.trace := context.trace * 100 + 13;
                        }
                    }
                    state Run parallel {
                        entry action {
                            rep language "JavaScript" /* trace = trace * 100 + 14;*/
                            assign context.trace := context.trace * 100 + 14;
                        }
                        exit action {
                            rep language "JavaScript" /* trace = trace * 100 + 15;*/
                            assign context.trace := context.trace * 100 + 15;
                        }
                        state pace {
                            #StateMachines::junction state Deep;
                            #StateMachines::junction state Out;
                            entry; then Slow;
                            state Slow;
                            state Fast {
                                entry action {
                                    rep language "JavaScript" /* trace = trace * 100 + 17;*/
                                    assign context.trace := context.trace * 100 + 17;
                                }
                            }
                            transition first Deep
                                do action {
                                    rep language "JavaScript" /* trace = trace * 100 + 21;*/
                                    assign context.trace := context.trace * 100 + 21;
                                }
                                then Fast;
                            transition first Fast accept Back
                                do action {
                                    rep language "JavaScript" /* trace = trace * 100 + 22;*/
                                    assign context.trace := context.trace * 100 + 22;
                                }
                                then Out;
                        }
                    }
                    #StateMachines::shallowHistory state H;
                    transition first Prep accept Next then Run;
                    transition first Start
                        do action {
                            rep language "JavaScript" /* trace = trace * 100 + 23;*/
                            assign context.trace := context.trace * 100 + 23;
                        }
                        then Run;
                    /* not migrated: Transition (_tThrough) — the source 'Through' has no v2 form: (_tThrough) leads from the entry point straight to the exit point 'Leave' of the same state, crossing it without settling in it; the runtime would then run neither its entry nor its exit behavior */
                    transition first Run accept Finish
                        do action {
                            rep language "JavaScript" /* trace = trace * 100 + 24;*/
                            assign context.trace := context.trace * 100 + 24;
                        }
                        then Leave;
                    transition first steps.Run.pace.Out
                        do action {
                            rep language "JavaScript" /* trace = trace * 100 + 25;*/
                            assign context.trace := context.trace * 100 + 25;
                        }
                        then Prep;
                }
            }
            state Sync {
                entry action {
                    rep language "JavaScript" /* trace = trace * 100 + 31;*/
                    assign context.trace := context.trace * 100 + 31;
                }
                then regions;
                exit action {
                    rep language "JavaScript" /* trace = trace * 100 + 32;*/
                    assign context.trace := context.trace * 100 + 32;
                }
                fork Both;
                join Gather;
                state regions parallel {
                    state a {
                        entry; then A0;
                        state A0;
                        state A1 {
                            entry action {
                                rep language "JavaScript" /* trace = trace * 100 + 33;*/
                                assign context.trace := context.trace * 100 + 33;
                            }
                            exit action {
                                rep language "JavaScript" /* trace = trace * 100 + 34;*/
                                assign context.trace := context.trace * 100 + 34;
                            }
                        }
                        transition first A0 accept Bump then A1;
                    }
                    state b {
                        entry; then B0;
                        state B0;
                        state B1 {
                            entry action {
                                rep language "JavaScript" /* trace = trace * 100 + 35;*/
                                assign context.trace := context.trace * 100 + 35;
                            }
                            exit action {
                                rep language "JavaScript" /* trace = trace * 100 + 36;*/
                                assign context.trace := context.trace * 100 + 36;
                            }
                        }
                        transition first B0 accept Bump then B1;
                    }
                }
                transition first regions then done;
                transition first Both then regions.a.A1;
                transition first regions.a.A1
                    do action {
                        rep language "JavaScript" /* trace = trace * 100 + 37;*/
                        assign context.trace := context.trace * 100 + 37;
                    }
                    then Gather;
                transition first Both then regions.b.B1;
                transition first regions.b.B1
                    do action {
                        rep language "JavaScript" /* trace = trace * 100 + 38;*/
                        assign context.trace := context.trace * 100 + 38;
                    }
                    then Gather;
                metadata MigrationMetadata::SynthesizedName about regions;
            }
            transition first Idle accept Go
                do action {
                    rep language "JavaScript" /* trace = trace * 100 + 41;*/
                    assign context.trace := context.trace * 100 + 41;
                }
                then Work.steps.Start;
            transition first Idle accept Go if false then Work;
            transition first Idle accept Enter then Work;
            transition first Idle accept Dive
                do action {
                    rep language "JavaScript" /* trace = trace * 100 + 42;*/
                    assign context.trace := context.trace * 100 + 42;
                }
                then Work.steps.Run.pace.Deep;
            transition first Idle accept Resume then Work.steps.H;
            /* not migrated: Transition (_tSkip) — the target 'Through' has no v2 form: (_tThrough) leads from the entry point straight to the exit point 'Leave' of the same state, crossing it without settling in it; the runtime would then run neither its entry nor its exit behavior */
            transition first Work.steps.Leave
                do action {
                    rep language "JavaScript" /* trace = trace * 100 + 43;*/
                    assign context.trace := context.trace * 100 + 43;
                }
                then Idle;
            transition first Work accept Stop
                do action {
                    rep language "JavaScript" /* trace = trace * 100 + 44;*/
                    assign context.trace := context.trace * 100 + 44;
                }
                then Idle;
            transition first Idle accept Pair then Sync;
            transition first Idle accept Split then Sync.Both;
            transition first Sync.Gather
                do action {
                    rep language "JavaScript" /* trace = trace * 100 + 46;*/
                    assign context.trace := context.trace * 100 + 46;
                }
                then Idle;
        }
        exhibit state cycle : Cycle { in ref :>> context = this; }
    }
    private import StateMachines::*;
}
