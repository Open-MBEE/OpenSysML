package Model {
    package Operations {
        part Operator;
        part alice :> Operator;
        use case Scan {
            include Focus;
        }
        use case Focus;
        occurrence def Console {
            ref use case current :> Scan;
            ref part user :> Operator;
            ref occurrence panel : Panel;
        }
        occurrence def Panel {
            ref occurrence console : Console;
        }
        connection def PanelToConsole {
            end panel : Panel crosses console.panel;
            end console : Console crosses panel.console;
        }
        occurrence panel : Panel;
        occurrence console : Console;
        connection 'panel to console' : PanelToConsole connect panel to console;
        connection 'Scan includes Focus' connect Scan to Focus;
        metadata MigrationMetadata::SynthesizedName about PanelToConsole, 'panel to console';
    }
    package Tables {
        view Classifiers {
            expose 'Classifiers Document';
            render Views::asElementTable;
        }
        calc def 'Classifiers Rows' :> DocumentQueries::Query {
            in candidates : KerML::Root::Element[0..*] ordered = DocumentQueries::Descendants(
                source = DocumentQueries::Named(qualifiedName = ("Model::Operations")));
            DocumentQueries::Project(
                source = DocumentQueries::OrderBy(
                    source = DocumentQueries::Union(
                        source = DocumentQueries::WhereType(source = candidates, type = ("Definition", "ViewUsage", "ViewpointUsage")),
                        other = DocumentQueries::Except(
                            source = DocumentQueries::Named(qualifiedName = ("Model::Operations::Operator", "Model::Operations::Scan", "Model::Operations::Focus")),
                            exclude = DocumentQueries::Except(
                                source = DocumentQueries::Named(qualifiedName = ("Model::Operations::Operator", "Model::Operations::Scan", "Model::Operations::Focus")),
                                exclude = candidates))),
                    property = "qualifiedName",
                    direction = "ascending",
                    missing = "last",
                    multiple = "first"),
                properties = ("qualifiedName"))
        }
        part def 'Classifiers Document' :> DocumentQueries::Document {
            attribute redefines title = "Classifiers";
            part rows : DocumentQueries::Table {
                attribute redefines caption = "Classifiers";
                calc rows : 'Classifiers Rows';
            }
        }
        view Types {
            expose 'Types Document';
            render Views::asElementTable;
        }
        calc def 'Types Rows' :> DocumentQueries::Query {
            in candidates : KerML::Root::Element[0..*] ordered = DocumentQueries::Descendants(
                source = DocumentQueries::Named(qualifiedName = ("Model::Operations")));
            DocumentQueries::Project(
                source = DocumentQueries::OrderBy(
                    source = DocumentQueries::Union(
                        source = DocumentQueries::WhereType(source = candidates, type = ("Definition", "ViewUsage", "ViewpointUsage")),
                        other = DocumentQueries::Except(
                            source = DocumentQueries::Named(qualifiedName = ("Model::Operations::Operator", "Model::Operations::Scan", "Model::Operations::Focus")),
                            exclude = DocumentQueries::Except(
                                source = DocumentQueries::Named(qualifiedName = ("Model::Operations::Operator", "Model::Operations::Scan", "Model::Operations::Focus")),
                                exclude = candidates))),
                    property = "qualifiedName",
                    direction = "ascending",
                    missing = "last",
                    multiple = "first"),
                properties = ("qualifiedName"))
        }
        part def 'Types Document' :> DocumentQueries::Document {
            attribute redefines title = "Types";
            part rows : DocumentQueries::Table {
                attribute redefines caption = "Types";
                calc rows : 'Types Rows';
            }
        }
        view Namespaces {
            expose 'Namespaces Document';
            render Views::asElementTable;
        }
        calc def 'Namespaces Rows' :> DocumentQueries::Query {
            in candidates : KerML::Root::Element[0..*] ordered = DocumentQueries::Descendants(
                source = DocumentQueries::Named(qualifiedName = ("Model::Operations")));
            DocumentQueries::Project(
                source = DocumentQueries::OrderBy(
                    source = DocumentQueries::Union(
                        source = DocumentQueries::WhereType(source = candidates, type = ("Package", "Definition", "ViewUsage", "ViewpointUsage", "StateUsage")),
                        other = DocumentQueries::Except(
                            source = DocumentQueries::Named(qualifiedName = ("Model::Operations::Operator", "Model::Operations::Scan", "Model::Operations::Focus")),
                            exclude = DocumentQueries::Except(
                                source = DocumentQueries::Named(qualifiedName = ("Model::Operations::Operator", "Model::Operations::Scan", "Model::Operations::Focus")),
                                exclude = candidates))),
                    property = "qualifiedName",
                    direction = "ascending",
                    missing = "last",
                    multiple = "first"),
                properties = ("qualifiedName"))
        }
        part def 'Namespaces Document' :> DocumentQueries::Document {
            attribute redefines title = "Namespaces";
            part rows : DocumentQueries::Table {
                attribute redefines caption = "Namespaces";
                calc rows : 'Namespaces Rows';
            }
        }
        view 'Packageable Elements' {
            expose 'Packageable Elements Document';
            render Views::asElementTable;
        }
        calc def 'Packageable Elements Rows' :> DocumentQueries::Query {
            in candidates : KerML::Root::Element[0..*] ordered = DocumentQueries::Descendants(
                source = DocumentQueries::Named(qualifiedName = ("Model::Operations")));
            DocumentQueries::Project(
                source = DocumentQueries::OrderBy(
                    source = DocumentQueries::Union(
                        source = DocumentQueries::Union(
                            source = DocumentQueries::WhereType(source = candidates, type = ("Package", "Definition", "ViewUsage", "ViewpointUsage", "Dependency", "SatisfyRequirementUsage", "AllocationUsage")),
                            other = DocumentQueries::Except(
                                source = DocumentQueries::Named(qualifiedName = ("Model::Operations::Operator", "Model::Operations::Scan", "Model::Operations::Focus")),
                                exclude = DocumentQueries::Except(
                                    source = DocumentQueries::Named(qualifiedName = ("Model::Operations::Operator", "Model::Operations::Scan", "Model::Operations::Focus")),
                                    exclude = candidates))),
                        other = DocumentQueries::Except(
                            source = DocumentQueries::Except(
                                source = DocumentQueries::Except(
                                    source = DocumentQueries::WhereType(source = candidates, type = ("Usage")),
                                    exclude = DocumentQueries::Union(
                                        source = DocumentQueries::WhereType(source = candidates, type = ("ConnectionUsage")),
                                        other = DocumentQueries::WhereType(source = candidates, type = ("MetadataUsage")))),
                                exclude = DocumentQueries::Descendants(
                                    source = DocumentQueries::WhereType(
                                        source = DocumentQueries::Union(
                                            source = DocumentQueries::Named(qualifiedName = ("Model::Operations")),
                                            other = DocumentQueries::Descendants(
                                                source = DocumentQueries::Union(
                                                    source = DocumentQueries::WhereType(
                                                        source = DocumentQueries::Named(qualifiedName = ("Model::Operations")),
                                                        type = ("Package")),
                                                    other = DocumentQueries::WhereType(source = candidates, type = ("Package"))),
                                                maxDepth = 1)),
                                        type = ("Type")))),
                            exclude = DocumentQueries::Named(qualifiedName = ("Model::Operations::console", "Model::Operations::panel")))),
                    property = "qualifiedName",
                    direction = "ascending",
                    missing = "last",
                    multiple = "first"),
                properties = ("qualifiedName"))
        }
        part def 'Packageable Elements Document' :> DocumentQueries::Document {
            attribute redefines title = "Packageable Elements";
            part rows : DocumentQueries::Table {
                attribute redefines caption = "Packageable Elements";
                calc rows : 'Packageable Elements Rows';
            }
        }
        view Actors {
            expose 'Actors Document';
            render Views::asElementTable;
        }
        calc def 'Actors Rows' :> DocumentQueries::Query {
            in candidates : KerML::Root::Element[0..*] ordered = DocumentQueries::Descendants(
                source = DocumentQueries::Named(qualifiedName = ("Model::Operations")));
            DocumentQueries::Project(
                source = DocumentQueries::OrderBy(
                    source = DocumentQueries::Except(
                        source = DocumentQueries::Named(qualifiedName = ("Model::Operations::Operator")),
                        exclude = DocumentQueries::Except(
                            source = DocumentQueries::Named(qualifiedName = ("Model::Operations::Operator")),
                            exclude = candidates)),
                    property = "qualifiedName",
                    direction = "ascending",
                    missing = "last",
                    multiple = "first"),
                properties = ("qualifiedName"))
        }
        part def 'Actors Document' :> DocumentQueries::Document {
            attribute redefines title = "Actors";
            part rows : DocumentQueries::Table {
                attribute redefines caption = "Actors";
                calc rows : 'Actors Rows';
            }
        }
        view 'Use Cases' {
            expose 'Use Cases Document';
            render Views::asElementTable;
        }
        calc def 'Use Cases Rows' :> DocumentQueries::Query {
            in candidates : KerML::Root::Element[0..*] ordered = DocumentQueries::Descendants(
                source = DocumentQueries::Named(qualifiedName = ("Model::Operations")));
            DocumentQueries::Project(
                source = DocumentQueries::OrderBy(
                    source = DocumentQueries::Except(
                        source = DocumentQueries::Named(qualifiedName = ("Model::Operations::Scan", "Model::Operations::Focus")),
                        exclude = DocumentQueries::Except(
                            source = DocumentQueries::Named(qualifiedName = ("Model::Operations::Scan", "Model::Operations::Focus")),
                            exclude = candidates)),
                    property = "qualifiedName",
                    direction = "ascending",
                    missing = "last",
                    multiple = "first"),
                properties = ("qualifiedName"))
        }
        part def 'Use Cases Document' :> DocumentQueries::Document {
            attribute redefines title = "Use Cases";
            part rows : DocumentQueries::Table {
                attribute redefines caption = "Use Cases";
                calc rows : 'Use Cases Rows';
            }
        }
        view 'Instance Specifications' {
            expose 'Instance Specifications Document';
            render Views::asElementTable;
        }
        calc def 'Instance Specifications Rows' :> DocumentQueries::Query {
            in candidates : KerML::Root::Element[0..*] ordered = DocumentQueries::Descendants(
                source = DocumentQueries::Named(qualifiedName = ("Model::Operations")));
            DocumentQueries::Project(
                source = DocumentQueries::OrderBy(
                    source = DocumentQueries::Except(
                        source = DocumentQueries::Except(
                            source = DocumentQueries::Except(
                                source = DocumentQueries::Except(
                                    source = DocumentQueries::WhereType(source = candidates, type = ("Usage")),
                                    exclude = DocumentQueries::Union(
                                        source = DocumentQueries::WhereType(source = candidates, type = ("ConnectionUsage")),
                                        other = DocumentQueries::WhereType(source = candidates, type = ("MetadataUsage")))),
                                exclude = DocumentQueries::Named(qualifiedName = ("Model::Operations::Operator", "Model::Operations::Scan", "Model::Operations::Focus"))),
                            exclude = DocumentQueries::Descendants(
                                source = DocumentQueries::WhereType(
                                    source = DocumentQueries::Union(
                                        source = DocumentQueries::Named(qualifiedName = ("Model::Operations")),
                                        other = DocumentQueries::Descendants(
                                            source = DocumentQueries::Union(
                                                source = DocumentQueries::WhereType(
                                                    source = DocumentQueries::Named(qualifiedName = ("Model::Operations")),
                                                    type = ("Package")),
                                                other = DocumentQueries::WhereType(source = candidates, type = ("Package"))),
                                            maxDepth = 1)),
                                    type = ("Type")))),
                        exclude = DocumentQueries::Named(qualifiedName = ("Model::Operations::console", "Model::Operations::panel"))),
                    property = "qualifiedName",
                    direction = "ascending",
                    missing = "last",
                    multiple = "first"),
                properties = ("qualifiedName"))
        }
        part def 'Instance Specifications Document' :> DocumentQueries::Document {
            attribute redefines title = "Instance Specifications";
            part rows : DocumentQueries::Table {
                attribute redefines caption = "Instance Specifications";
                calc rows : 'Instance Specifications Rows';
            }
        }
        view Operators {
            expose 'Operators Document';
            render Views::asElementTable;
        }
        calc def 'Operators Rows' :> DocumentQueries::Query {
            DocumentQueries::Project(
                source = DocumentQueries::OrderBy(
                    source = DocumentQueries::Except(
                        source = DocumentQueries::Except(
                            source = DocumentQueries::WhereType(
                                source = DocumentQueries::Except(
                                    source = DocumentQueries::WhereType(
                                        source = DocumentQueries::Descendants(
                                            source = DocumentQueries::Named(qualifiedName = ("Model::Operations"))),
                                        type = ("Model::Operations::Operator")),
                                    exclude = DocumentQueries::Named(qualifiedName = ("Model::Operations::Operator"))),
                                type = ("Usage")),
                            exclude = DocumentQueries::Descendants(
                                source = DocumentQueries::WhereType(
                                    source = DocumentQueries::Union(
                                        source = DocumentQueries::Named(qualifiedName = ("Model::Operations")),
                                        other = DocumentQueries::Descendants(
                                            source = DocumentQueries::Union(
                                                source = DocumentQueries::WhereType(
                                                    source = DocumentQueries::Named(qualifiedName = ("Model::Operations")),
                                                    type = ("Package")),
                                                other = DocumentQueries::WhereType(
                                                    source = DocumentQueries::Descendants(
                                                        source = DocumentQueries::Named(qualifiedName = ("Model::Operations"))),
                                                    type = ("Package"))),
                                            maxDepth = 1)),
                                    type = ("Type")))),
                        exclude = DocumentQueries::Named(qualifiedName = ("Model::Operations::console", "Model::Operations::panel"))),
                    property = "qualifiedName",
                    direction = "ascending",
                    missing = "last",
                    multiple = "first"),
                properties = ("qualifiedName"))
        }
        part def 'Operators Document' :> DocumentQueries::Document {
            attribute redefines title = "Operators";
            part rows : DocumentQueries::Table {
                attribute redefines caption = "Operators";
                calc rows : 'Operators Rows';
            }
        }
        view 'Console Operators' {
            expose 'Console Operators Document';
            render Views::asElementTable;
        }
        calc def 'Console Operators Rows' :> DocumentQueries::Query {
            DocumentQueries::Project(
                source = DocumentQueries::OrderBy(
                    source = DocumentQueries::Except(
                        source = DocumentQueries::Except(
                            source = DocumentQueries::WhereType(
                                source = DocumentQueries::Except(
                                    source = DocumentQueries::WhereType(
                                        source = DocumentQueries::Descendants(
                                            source = DocumentQueries::Named(qualifiedName = ("Model::Operations::Console"))),
                                        type = ("Model::Operations::Operator")),
                                    exclude = DocumentQueries::Named(qualifiedName = ("Model::Operations::Operator"))),
                                type = ("Usage")),
                            exclude = DocumentQueries::Descendants(
                                source = DocumentQueries::WhereType(
                                    source = DocumentQueries::Union(
                                        source = DocumentQueries::Named(qualifiedName = ("Model::Operations::Console")),
                                        other = DocumentQueries::Descendants(
                                            source = DocumentQueries::Union(
                                                source = DocumentQueries::WhereType(
                                                    source = DocumentQueries::Named(qualifiedName = ("Model::Operations::Console")),
                                                    type = ("Package")),
                                                other = DocumentQueries::WhereType(
                                                    source = DocumentQueries::Descendants(
                                                        source = DocumentQueries::Named(qualifiedName = ("Model::Operations::Console"))),
                                                    type = ("Package"))),
                                            maxDepth = 1)),
                                    type = ("Type")))),
                        exclude = DocumentQueries::Named(qualifiedName = ("Model::Operations::console", "Model::Operations::panel"))),
                    property = "qualifiedName",
                    direction = "ascending",
                    missing = "last",
                    multiple = "first"),
                properties = ("qualifiedName"))
        }
        part def 'Console Operators Document' :> DocumentQueries::Document {
            attribute redefines title = "Console Operators";
            part rows : DocumentQueries::Table {
                attribute redefines caption = "Console Operators";
                calc rows : 'Console Operators Rows';
            }
        }
    }
}
