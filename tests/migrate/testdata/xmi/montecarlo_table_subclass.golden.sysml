package Model {
    part def 'Base Analysis' {
        attribute t : ScalarValues::Real;
    }
    analysis def 'Base Analysis Monte Carlo' :> Simulation::MonteCarlo {
        subject analysed : 'Base Analysis';
        /* one run performs no behavior: neither Base Analysis nor any general of it has a classifier behavior */
        attribute :>> observed : ScalarValues::Real = analysed.t;
        return Mean : ScalarValues::Real[1] = mean;
    }
    part def 'Fast Analysis' :> 'Base Analysis';
    package Results {
        part 'fast analysis of 9 runs' : 'Fast Analysis' {
            attribute :>> t = 4.0;
            analysis 'Monte Carlo' : 'Base Analysis Monte Carlo' {
                subject :>> analysed = 'fast analysis of 9 runs';
                out :>> runs = 9;
            }
        }
        view 'Fast Statistics' {
            expose 'fast analysis of 9 runs';
            expose 'Fast Statistics Document';
            render Views::asElementTable;
        }
        calc def 'Fast Statistics Rows' :> DocumentQueries::Query {
            DocumentQueries::Project(
                source = DocumentQueries::OrderBy(
                    source = DocumentQueries::Except(
                        source = DocumentQueries::WhereType(
                            source = DocumentQueries::WhereType(
                                source = DocumentQueries::Descendants(
                                    source = DocumentQueries::Named(qualifiedName = ("Model::Results"))),
                                type = ("Model::Fast Analysis")),
                            type = ("Usage")),
                        exclude = DocumentQueries::Descendants(
                            source = DocumentQueries::WhereType(
                                source = DocumentQueries::Union(
                                    source = DocumentQueries::Named(qualifiedName = ("Model::Results")),
                                    other = DocumentQueries::Descendants(
                                        source = DocumentQueries::Union(
                                            source = DocumentQueries::WhereType(
                                                source = DocumentQueries::Named(qualifiedName = ("Model::Results")),
                                                type = ("Package")),
                                            other = DocumentQueries::WhereType(
                                                source = DocumentQueries::Descendants(
                                                    source = DocumentQueries::Named(qualifiedName = ("Model::Results"))),
                                                type = ("Package"))),
                                        maxDepth = 1)),
                                type = ("Type")))),
                    property = "'Monte Carlo'.runs",
                    direction = "descending",
                    missing = "last",
                    multiple = "first"),
                properties = ("name"),
                columns = (
                    DocumentQueries::Column(name = "N", path = "'Monte Carlo'.runs")))
        }
        part def 'Fast Statistics Document' :> DocumentQueries::Document {
            attribute redefines title = "Fast Statistics";
            part rows : DocumentQueries::Table {
                attribute redefines caption = "Fast Statistics";
                calc rows : 'Fast Statistics Rows';
            }
        }
    }
}
