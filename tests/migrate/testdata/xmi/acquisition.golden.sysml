package Model {
    action def 'Group 0' {
        @Simulation::Configuration {
            runs = 6;
            draws = Simulation::DrawPolicy::random;
            timeVariable = "simtime";
        }
    }
    action def 'Group 1' {
        @Simulation::Configuration {
            runs = 1;
            draws = Simulation::DrawPolicy::max;
        }
    }
    part def TCS {
        attribute i : ScalarValues::Integer default = 0;
        attribute Retries : ScalarValues::Integer default = 4;
        attribute GS_Found : ScalarValues::Boolean default = false;
        attribute 'Guide Star Lost' : ScalarValues::Boolean default = false;
        attribute ditSetup : ScalarValues::Real default = 2.5;
    }
    part def Observatory {
        part tcs : TCS;
        attribute Time_Acq_Total : ScalarValues::Real default = 0.0;
        action acquire {
            attribute 'Time_Loop start' : ScalarValues::Real [0..1];
            attribute Time_Loop : ScalarValues::Real [0..1];
            attribute 'Time_Between start' : ScalarValues::Real [0..1];
            attribute Time_Between : ScalarValues::Real [0..1];
            attribute 'Time_Attempt start' : ScalarValues::Real [0..1];
            attribute Time_Attempt : ScalarValues::Real [0..1];
            attribute 'Time_Never start' : ScalarValues::Real [0..1];
            attribute Time_Never : ScalarValues::Real [0..1];
            attribute 'Time_Unfinished start' : ScalarValues::Real [0..1];
            attribute Time_Unfinished : ScalarValues::Real [0..1];
            attribute 'Time_Run start' : ScalarValues::Real [0..1];
            attribute Time_Run : ScalarValues::Real [0..1];
            attribute 'Time_Pass start' : ScalarValues::Real [0..1];
            attribute Time_Pass : ScalarValues::Real [0..1];
            attribute 'Time_Drop start' : ScalarValues::Real [0..1];
            attribute Time_Drop : ScalarValues::Real [0..1];
            first start then stamp9;
            action stamp9 {
                assign 'Time_Run start' := localClock.currentTime;
            }
            first stamp9 then 'start timer';
            action 'start timer' {
                rep language "JavaScript" /* Time_Acq_Total = simtime;*/
                assign Time_Acq_Total := localClock.currentTime;
            }
            first 'start timer' then seed;
            action seed {
                in Retries : ScalarValues::Integer[1] = 2;
                rep language "JavaScript" /* GS_Found = Retries < 1;*/
                assign tcs.GS_Found := Retries < 1;
            }
            first seed then stamp;
            action stamp {
                assign 'Time_Loop start' := localClock.currentTime;
                assign 'Time_Unfinished start' := localClock.currentTime;
                assign 'Time_Pass start' := localClock.currentTime;
                assign 'Time_Drop start' := localClock.currentTime;
            }
            first stamp then 'first attempt';
            action 'first attempt' {
                rep language "JavaScript" /* i = 1;
                 * GS_Found = false;*/
                assign tcs.i := 1;
                assign tcs.GS_Found := false;
            }
            first 'first attempt' then stamp3;
            action stamp3 {
                assign 'Time_Between start' := localClock.currentTime;
            }
            first stamp3 then 'merge';
            merge 'merge';
            first 'merge' then stamp5;
            action wait accept after tcs.ditSetup [SI::s];
            first wait then attempt;
            action stamp5 {
                assign 'Time_Attempt start' := localClock.currentTime;
            }
            first stamp5 then wait;
            action attempt;
            first attempt then stamp6;
            action stamp6 {
                if 'Time_Attempt start'->SequenceFunctions::notEmpty() {
                    assign Time_Attempt := localClock.currentTime - 'Time_Attempt start';
                }
            }
            first stamp6 then 'fork';
            fork 'fork';
            first 'fork' then 'decide';
            first 'fork' then merge2;
            first 'fork' then merge3;
            action stamp11 {
                if 'Time_Pass start'->SequenceFunctions::notEmpty() {
                    assign Time_Pass := localClock.currentTime - 'Time_Pass start';
                }
            }
            first stamp11 then done;
            merge merge2;
            first merge2 then stamp11;
            action stamp12 {
                if 'Time_Drop start'->SequenceFunctions::notEmpty() {
                    assign Time_Drop := localClock.currentTime - 'Time_Drop start';
                }
            }
            first stamp12 then done;
            merge merge3;
            first merge3 then stamp12;
            decide 'decide';
            first 'decide' if tcs.i >= tcs.Retries then stamp4;
            first 'decide' if not tcs.GS_Found and not tcs.'Guide Star Lost' and tcs.i < tcs.Retries then 'next attempt';
            first 'decide' if false then stamp7;
            action stamp4 {
                if 'Time_Between start'->SequenceFunctions::notEmpty() {
                    assign Time_Between := localClock.currentTime - 'Time_Between start';
                }
            }
            first stamp4 then 'guide star found';
            action 'guide star found' {
                rep language "JavaScript" /* GS_Found = true;*/
                assign tcs.GS_Found := true;
            }
            first 'guide star found' then stamp2;
            action stamp2 {
                if 'Time_Loop start'->SequenceFunctions::notEmpty() {
                    assign Time_Loop := localClock.currentTime - 'Time_Loop start';
                }
                if 'Time_Never start'->SequenceFunctions::notEmpty() {
                    assign Time_Never := localClock.currentTime - 'Time_Never start';
                }
            }
            first stamp2 then merge4;
            action 'next attempt' {
                rep language "JavaScript" /* i += 1;*/
                assign tcs.i := tcs.i + 1;
            }
            first 'next attempt' then 'merge';
            action stamp7 {
                assign 'Time_Never start' := localClock.currentTime;
            }
            first stamp7 then abort;
            action abort {
                rep language "JavaScript" /* GS_Found = false;*/
                assign tcs.GS_Found := false;
            }
            first abort then stamp8;
            action stamp8 {
                if 'Time_Unfinished start'->SequenceFunctions::notEmpty() {
                    assign Time_Unfinished := localClock.currentTime - 'Time_Unfinished start';
                }
            }
            first stamp8 then fork2;
            fork fork2;
            first fork2 then merge3;
            first fork2 then merge2;
            action 'stop timer' {
                rep language "JavaScript" /* Time_Acq_Total = simtime - Time_Acq_Total;*/
                assign Time_Acq_Total := localClock.currentTime - Time_Acq_Total;
            }
            first 'stop timer' then stamp10;
            merge merge4;
            first merge4 then 'stop timer';
            action stamp10 {
                if 'Time_Run start'->SequenceFunctions::notEmpty() {
                    assign Time_Run := localClock.currentTime - 'Time_Run start';
                }
            }
            first stamp10 then final;
            action final terminate;
            /* partition 'Telescope Control' represents Observatory::tcs: seed, first attempt, attempt, decide, guide star found, next attempt, abort */
            metadata MigrationMetadata::SynthesizedName about stamp9, stamp, stamp3, 'merge', wait, stamp5, stamp6, 'fork', stamp11, merge2, stamp12, merge3, 'decide', stamp4, stamp2, stamp7, stamp8, fork2, merge4, stamp10, final;
            metadata MigrationMetadata::StandIn about stamp9, stamp, stamp3, wait, stamp5, stamp6, stamp11, merge2, stamp12, merge3, stamp4, stamp2, stamp7, stamp8, fork2, stamp10;
        }
    }
}
