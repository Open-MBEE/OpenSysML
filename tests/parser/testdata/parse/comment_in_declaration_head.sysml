package test {
	// A comment inside a declaration head is trivia: the words in it name
	// neither the declaration's kind nor its name.
	attribute // the flow rate
		rate : Real;
	part /* a state */ def Housing;
	use case /* the case */ def Mission;
}
