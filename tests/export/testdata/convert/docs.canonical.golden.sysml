package Documented {
    doc /* what this package is for */
    part def Wheel {
        doc /* one wheel */
    }
    comment about Wheel /* a note on wheels */
    rep asJava language "java" /* class Wheel {} */
}
