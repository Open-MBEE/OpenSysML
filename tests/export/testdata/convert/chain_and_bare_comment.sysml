package Chains {
    comment /* a comment with no name and no about clause */
    part def V {
        part e : V;
    }
    part v : V;
    part chain c : V;
    comment Named about V /* a comment that is identified */
}
