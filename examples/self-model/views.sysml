// The views that present the architecture, one per rendering kind, plus the
// filtered layer views.
package OpenSysMLViews {
    private import Views::*;
    private import StandardViewDefinitions::*;
    private import OpenSysMLArtifacts::*;

    viewpoint def MaintainerPerspective {
        frame concern latency : OpenSysMLInvariants::KeystrokeLatency;
    }

    viewpoint maintainerPerspective : MaintainerPerspective;

    view pipelineStructure {
        doc /* The analysis pipeline: stages, channels and the artifacts flowing. */
        expose OpenSysMLPipeline::AnalysisPipeline;
        render asInterconnectionDiagram;
    }

    view toolchainStructure {
        doc /* Surfaces, clients and oracles around the pipeline. */
        expose OpenSysMLSurfaces::Toolchain;
        render asInterconnectionDiagram;
    }

    view documentPipeline {
        expose OpenSysMLSurfaces::DocumentPipeline;
        render asInterconnectionDiagram;
    }

    view documentFlow : ActionFlowView {
        doc /* One document rendered, and the three forms it branches to. */
        expose OpenSysMLSurfaces::RenderDocument;
    }

    view stageTable {
        doc /* Every stage with the Go package that implements it. */
        expose OpenSysMLPipeline::AnalysisPipeline;
        render asElementTable;
    }

    view invariantTable {
        expose OpenSysMLInvariants::**[@OpenSysMLArtifacts::Invariant];
        render asElementTable;
    }

    view analysisFlow : ActionFlowView {
        expose OpenSysMLBehavior::AnalyzeDocument;
    }

    view editFlow : ActionFlowView {
        expose OpenSysMLBehavior::ServeEdit;
    }

    view libraryLoadFlow : ActionFlowView {
        doc /* The bundled library loaded: from its snapshot, or from its files. */
        expose OpenSysMLBehavior::LoadLibrary;
    }

    view calcInvocationFlow : ActionFlowView {
        doc /* One calc invoked: compiled when it may be, on the evaluator otherwise. */
        expose OpenSysMLBehavior::InvokeCalc;
    }

    view instanceLayer {
        doc /* The instance layer: a type's schema once, objects on demand, every value read lazily and admitted. */
        expose OpenSysMLExecution::InstanceModel;
        render asInterconnectionDiagram;
    }

    view featureReadFlow : ActionFlowView {
        doc /* One feature read: the case the feature is in decides how its value is made. */
        expose OpenSysMLBehavior::ReadFeatureValue;
    }

    view actionExecution : SequenceView {
        doc /* One action executed: lowered, stepped, scheduled, evaluated, read and written. */
        expose OpenSysMLExecution::ExecuteAction;
    }

    view tierStates : StateTransitionView {
        expose OpenSysMLBehavior::TierProgression;
    }

    view runtimeTiers : StateTransitionView {
        expose OpenSysMLBehavior::RuntimeTiers;
    }

    view tokenFlow : StateTransitionView {
        expose OpenSysMLBehavior::TokenFlow;
    }

    view eventDispatch : StateTransitionView {
        expose OpenSysMLBehavior::EventDispatch;
    }

    view budgetExhaustion : StateTransitionView {
        doc /* Eight budgets, eight ways a run can end early, each naming itself. */
        expose OpenSysMLBehavior::BudgetExhaustion;
    }

    view analysisFramework {
        doc /* One contract for every question: kinds, evidence, registry, dispatch, budget, workers, engines. */
        expose OpenSysMLPipeline::AnalysisFramework;
        render asInterconnectionDiagram;
    }

    view engineTable {
        doc /* The engines this build registers, what each answers and how strongly. */
        expose OpenSysMLPipeline::AnalysisFramework;
        render asElementTable;
    }

    view questionFlow : ActionFlowView {
        doc /* One question answered: selection, coverage, the run, and what the plan records. */
        expose OpenSysMLBehavior::AnswerQuestion;
    }

    view exploreFlow : ActionFlowView {
        doc /* A behavior's outcomes explored over a fleet of workers, proved or observed. */
        expose OpenSysMLBehavior::ExploreOutcomes;
    }

    view evidenceLadder : StateTransitionView {
        doc /* The five strengths of an answer, and what earns each. */
        expose OpenSysMLBehavior::EvidenceLadder;
    }

    view workerLifecycle : StateTransitionView {
        doc /* A plan's worker: warmed once for its job, a fresh context per run. */
        expose OpenSysMLBehavior::WorkerLifecycle;
    }

    view snapshotLifecycle : StateTransitionView {
        doc /* A snapshot as a mark between steps, and the two asks it refuses. */
        expose OpenSysMLBehavior::SnapshotLifecycle;
    }

    view editorPipeline {
        doc /* What an editor reaches: highlighting, fixes, suggestions, edits. */
        expose OpenSysMLSurfaces::EditorPipeline;
        render asInterconnectionDiagram;
    }

    view renderingKinds {
        doc /* Every rendering kind the view engine recognizes, and which it produces. */
        expose OpenSysMLSurfaces::ViewEngine;
        render asElementTable;
    }

    view surfaceTable {
        doc /* Every surface over the pipeline, with its command and protocol. */
        expose OpenSysMLSurfaces::Toolchain;
        render asElementTable;
    }

    view markupParsers {
        doc /* The markup languages a prose body may be written in, and which leave the process. */
        expose OpenSysMLSurfaces::DocumentPipeline;
        render asElementTable;
    }

    view identityPath {
        doc /* How an element's repository id reaches RDF and comes back. */
        expose OpenSysMLIdentity::IdentityPath;
        render asInterconnectionDiagram;
    }

    view identityRoundTrip : ActionFlowView {
        expose OpenSysMLIdentity::CarryIdentity;
    }

    view syncFlow : ActionFlowView {
        doc /* A local model diffed against its repository, keyed by effective id. */
        expose OpenSysMLIdentity::SyncModel;
    }

    view identityLayer {
        expose OpenSysMLIdentity::**[@OpenSysMLIdentity::Identity];
    }

    // The layer views, each reached by a filtered recursive expose.
    view frontendLayer {
        expose OpenSysMLPipeline::**[@OpenSysMLArtifacts::Frontend];
    }

    view semanticLayer {
        expose OpenSysMLPipeline::**[@OpenSysMLArtifacts::SemanticEngine];
    }

    view backendLayer {
        expose OpenSysMLPipeline::**[@OpenSysMLArtifacts::Backend];
    }

    view analysisLayer {
        expose OpenSysMLPipeline::**[@OpenSysMLArtifacts::Analysis];
    }

    view oracleLayer {
        expose OpenSysMLSurfaces::**[@OpenSysMLArtifacts::Oracle];
    }

    view overview {
        expose OpenSysMLSurfaces::opensysml;
        expose OpenSysMLSurfaces::Toolchain::lsp;
        view pipelineSubview :> pipelineStructure;

        satisfy maintainerPerspective;
    }

    // --- The query path ----------------------------------------------------

    // From a calc def over the library, through the compiler and the executor,
    // to the surfaces that show its rows or its outcome.
    view queryPath {
        expose OpenSysMLQueries::QueryPath;
        render asInterconnectionDiagram;
    }

    // One step evaluated: a value, a path error or a model error.
    view stepOutcome : StateTransitionView {
        expose OpenSysMLQueries::StepOutcome;
    }

    // The library's calc defs beside the plan operations they compile to.
    view libraryOperations {
        expose OpenSysMLQueries::QueryLibrary;
        render asElementTable;
    }
}
