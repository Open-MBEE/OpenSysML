// Invalid: 'ref' is a usage prefix; a definition prefix admits only 'abstract' or 'variation' (SysML.xtext:498 DefinitionPrefix, :563 BasicUsagePrefix).
package G74RefOnDefinition {
    ref part def R;
}
