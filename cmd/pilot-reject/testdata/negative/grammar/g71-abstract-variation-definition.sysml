// Invalid: 'abstract' and 'variation' are alternatives of one definition prefix, never both (SysML.xtext:490 BasicDefinitionPrefix).
package G71AbstractVariationDefinition {
    abstract variation part def V;
}
