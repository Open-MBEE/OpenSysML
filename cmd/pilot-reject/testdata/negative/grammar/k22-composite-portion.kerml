// Invalid: 'composite' and 'portion' are alternatives of one feature prefix, never both (KerML.xtext:514 BasicFeaturePrefix).
package K22CompositePortion {
    class A {
        composite portion feature j;
    }
}
