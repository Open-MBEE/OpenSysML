// Invalid: the 'composite' | 'portion' alternative of a feature prefix is optional but written at most once (KerML.xtext:514 BasicFeaturePrefix).
package K27RepeatedComposite {
    class A {
        composite composite feature j;
    }
}
