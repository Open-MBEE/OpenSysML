package ExactRationals {
	private import ScalarValues::*;

	attribute tenth : Rational = 0.1;
	attribute tenfold : Rational = tenth + tenth + tenth + tenth + tenth + tenth + tenth + tenth + tenth + tenth;
}
