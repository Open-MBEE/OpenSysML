// A definition specializing itself, the shortest specialization cycle. Kept as
// a probe because the pilot reports nothing for it (F4).
package 'Specialization Cycle Self Probe' {
	part def A specializes A;
}
