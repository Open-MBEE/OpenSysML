// Invalid: DoActionMember is a StateBodyItem; a part def body admits no 'do' (SysML.xtext StateBodyItem; pilot validateStateSubactionMembershioOwningType).
package G08DoOutsideStateBody {
    part def P {
        do a;
    }
}
