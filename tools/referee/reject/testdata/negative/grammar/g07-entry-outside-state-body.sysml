// Invalid: EntryActionMember is a StateBodyItem; a part def body admits no 'entry' (SysML.xtext StateBodyItem; pilot validateStateSubactionMembershioOwningType).
package G07EntryOutsideStateBody {
    part def P {
        entry a;
    }
}
