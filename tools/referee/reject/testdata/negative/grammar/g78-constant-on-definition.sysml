// Invalid: 'constant' is a usage prefix (SysML.xtext:560 RefPrefix); a definition prefix admits only 'abstract' or 'variation' (SysML.xtext:490 BasicDefinitionPrefix).
package G78ConstantOnDefinition {
    constant part def D;
}
