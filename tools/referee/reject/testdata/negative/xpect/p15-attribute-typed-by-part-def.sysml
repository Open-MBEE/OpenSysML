// Invalid: An attribute must be typed by attribute definitions (SysML 7.6 validateAttributeUsageType; pilot AttributeUsage_invalid.sysml.xt).
package P15AttributeTypedByPartDef {
    part def A;
    attribute a : A;
}
