// Invalid: An individual must be typed by one individual definition (SysML 7.9 validateOccurrenceUsageIndividualUsage; pilot IndividualUsage_Invalid.sysml.xt:39).
package P33IndividualTypedByPlainDef {
    part def B;
    individual b_1_1 : B;
}
