// Invalid: A calculation must be typed by one calculation definition (SysML 7.18 Calculations; pilot validateCalculationUsageType).
package S07CalcTypedByActionDef {
    action def AD;
    calc c : AD;
}
