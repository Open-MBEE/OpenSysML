// Invalid: A viewpoint must be typed by one viewpoint definition (SysML 7.25 Views and Viewpoints; pilot validateViewpointUsageType).
package S42ViewpointTypedByRequirementDef {
    requirement def RD;
    viewpoint vp : RD;
}
