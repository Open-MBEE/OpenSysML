// Invalid: A verification case must be typed by one verification case definition (SysML 7.23 Verification Cases; pilot validateVerificationCaseUsageType).
package S39VerificationTypedByCaseDef {
    case def CD;
    verification v : CD;
}
