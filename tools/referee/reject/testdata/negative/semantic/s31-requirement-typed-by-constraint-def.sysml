// Invalid: A requirement must be typed by one requirement definition (SysML 7.20 Requirements; pilot validateRequirementUsageType).
package S31RequirementTypedByConstraintDef {
    constraint def C;
    requirement r : C;
}
