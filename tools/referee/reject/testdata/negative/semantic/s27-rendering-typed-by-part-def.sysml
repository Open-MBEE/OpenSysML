// Invalid: A rendering must be typed by one rendering definition (SysML 7.25 Views and Viewpoints; pilot validateRenderingUsageType).
package S27RenderingTypedByPartDef {
    part def PD;
    rendering r : PD;
}
