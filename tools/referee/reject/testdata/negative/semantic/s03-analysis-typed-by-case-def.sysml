// Invalid: An analysis case must be typed by one analysis case definition (SysML 7.22 Analysis Cases; pilot validateAnalysisCaseUsageType).
package S03AnalysisTypedByCaseDef {
    case def CD;
    analysis a : CD;
}
