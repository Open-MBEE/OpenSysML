// Invalid: a type cannot difference exactly one type (KerML 8.3.3.1 validateTypeOwnedDifferencingNotOne; pilot validateOwnedDifferencingNotOne).
package K02DifferencesOneType {
    class A;
    class C differences A;
}
