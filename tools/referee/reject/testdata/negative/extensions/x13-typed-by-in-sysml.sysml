// Invalid: 'typed by' is the KerML spelling of a typing; a SysML usage spells it ':' or 'defined by' (KerML.xtext:600 TypedBy, SysML.xtext:392 TypedBy, :395 DefinedByKeyword).
package X13TypedByInSysML {
    part def P;
    part p typed by P;
}
