// Census: validateOccurrenceUsagePortionKind
// Case: violating
// Ours: e[portion-owner] Must be owned by an occurrence definition or usage.
// Pilot: e: Must be owned by an occurrence definition or usage.
package P { attribute def AD { timeslice t; } }
