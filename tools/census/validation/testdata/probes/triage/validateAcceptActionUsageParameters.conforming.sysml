// Census: validateAcceptActionUsageParameters
// Case: conforming
// Ours: e[unresolved] unresolved reference: x — did you mean RealFunctions::im::x, RealFunctio
// Pilot: e: Couldn't resolve reference to Type 'x'. | e: A usage must be typed by definitions.
action def A { accept x; }
