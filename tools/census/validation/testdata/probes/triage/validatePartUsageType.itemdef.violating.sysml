// Census: validatePartUsageType
// Case: violating
// Ours: e[part-usage-part-definition] A part must be typed by at least one part definition.
// Pilot: clean
item def ID; part def P { part p : ID; }
