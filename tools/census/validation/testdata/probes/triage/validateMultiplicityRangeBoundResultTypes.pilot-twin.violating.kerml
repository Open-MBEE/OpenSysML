// Census: validateMultiplicityRangeBoundResultTypes
// Case: violating
// Ours: e[multiplicity-bound-natural] Must have a Natural value
// Pilot: e: Must have a Natural value
package P {
  class C { feature f ["two"]; }
}
