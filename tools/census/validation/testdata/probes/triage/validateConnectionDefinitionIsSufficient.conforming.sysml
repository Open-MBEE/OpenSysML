// Census: validateConnectionDefinitionIsSufficient
// Case: conforming
// Ours: e[related-elements] Must have at least two related elements
// Pilot: e: Must have at least two related elements
connection def C;
