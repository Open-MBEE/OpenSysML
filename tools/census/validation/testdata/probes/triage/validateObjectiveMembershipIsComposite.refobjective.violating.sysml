// Census: validateObjectiveMembershipIsComposite
// Case: violating
// Ours: clean
// Pilot: e: no viable alternative at input 'ref' | e: extraneous input '}' expecting EOF
requirement def R; use case def U { ref objective o : R; }
