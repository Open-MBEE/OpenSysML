// Census: validateFeatureEndIsConstant
// Case: violating
// Ours: w[end-feature-multiplicity] End feature must have multiplicity 1: an end relates exactly one thing p
// Pilot: e: no viable alternative at input 'end'
package P { class A; class C { var end feature a : A; } }
