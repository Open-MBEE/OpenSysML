// Census: validateMultiplicityRangeBounds
// Case: violating
// Ours: e[multiplicity-range] multiplicity lower bound exceeds upper bound on a
// Pilot: clean
package P { class A; feature a : A [3..1]; }
