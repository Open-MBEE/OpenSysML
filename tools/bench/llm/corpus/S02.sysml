package Laptop {
    private import ScalarValues::*;

    part def Laptop {
        attribute serialNumber : String;
        attribute screenSizeInches : Real;
        attribute memoryGigabytes : Integer;
        attribute isTouchscreen : Boolean;
    }
}
