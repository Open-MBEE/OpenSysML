package Package {
    private import ISQ::*;
    private import SI::*;

    part def Parcel {
        attribute mass :> ISQ::mass = 2.5 [kg];
        attribute length :> ISQ::length = 0.4 [m];
    }
}
