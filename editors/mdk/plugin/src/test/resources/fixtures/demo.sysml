package Demo {
  requirement def MassLimit {
    attribute actual : ScalarValues::Real;
    require constraint { actual < 200.0 }
  }

  part def Vehicle {
    attribute mass : ScalarValues::Real = 100.0;
    part wheel : Wheel;
    constraint lightEnough { mass < 200.0 }
    constraint tiny { mass > 200.0 }
    requirement massLimit : MassLimit {
      attribute redefines actual = mass;
    }
  }

  part def Wheel;

  calc def twice { in x : ScalarValues::Integer; return : ScalarValues::Integer[1] = x * 2; }

  calc def Parts :> DocumentQueries::Query {
    DocumentQueries::Project(
      source = DocumentQueries::WhereType(
        source = DocumentQueries::Descendants(source = DocumentQueries::Named(qualifiedName = "Demo")),
        type = "PartDefinition"),
      properties = ("qualifiedName", "name"))
  }

  calc def PartsUnder :> DocumentQueries::Query {
    in root : KerML::Root::Element;
    in kind : ScalarValues::String = "PartDefinition";
    DocumentQueries::Project(
      source = DocumentQueries::WhereType(source = DocumentQueries::Descendants(source = root), type = kind),
      properties = ("qualifiedName", "name"))
  }

  calc def NoPorts :> PartsUnder {
    in redefines kind = "PortDefinition";
  }

  calc def Under :> DocumentQueries::Query {
    in roots : KerML::Root::Element[0..*];
    DocumentQueries::Project(source = DocumentQueries::Descendants(source = roots), properties = ("qualifiedName"))
  }

  calc def UnderPackages :> Under {
    in redefines roots : KerML::Root::Element;
  }

  calc def Unresolved :> DocumentQueries::Query {
    DocumentQueries::Project(source = DocumentQueries::Named(qualifiedName = "Demo::Nope"), properties = ("name"))
  }

  state def Lifecycle {
    entry; then off;
    state off;
    state on;
    transition off_on first off accept Start then on;
  }
}
